module wirelesshart-network-metrics {
	namespace "http://dei.uc.pt/yang/wirelesshart";
	
	prefix "na";

	organization "University of Coimbra";
	contact "draposo@dei.uc.pt";

	description "This module represent WirelessHART metrics shared in the network according to the standard";
	revision "2017-04-12" {
		description "Initial revision.";
		reference "NA";
	}
	container network-metrics {
		description "Container for WirelessHART network metrics";
		config false;
		list device-health{
			config false;
			key "macaddress";
			description "List the last report of each device";
			leaf macaddress {
				config false;
				type string;
				description "Mac address of device";
			}
			leaf packets-generated-by-device{
				config false;
				type uint16;
				description "Number of Packets generated by Device";
			}
			leaf packets-terminated-by-device{
				config false;
				type uint16;
				description "Number of Packets terminated by Device";
			}
			leaf dll-mic-failures{
				config false;
				type uint8;
				description "Number of Data Link Layer mic failures";
			}
			leaf nwk-mic-failures{
				config false;
				type uint8;
				description "Number of Network Link Layer Failures";
			}
			leaf power-status{
				config false;
				type int8;
				description "Power Status generated by Device";
			}
			leaf crc-errors{
				config false;
				type uint8;
				description "Number of CRC errors detected";
			}
		}
		list neighbour-health-list{
			config false;
			key "macaddress";
			description "List of linked neighbours";
			leaf macaddress {
				config false;
				type string;
				description "Mac address of device";
			}
			list neighbour{
				key "neighbour-macaddress";
				leaf neighbour-macaddress {
					config false;
					type string;
					description "Neighbor Mac address";
				}
				leaf mean-rsl{
					config false;
					type int8;
					description "Mean RSL to the neighbour";
				}
				leaf packets-transmitted-to-the-neighbour{
					config false;
					type uint16;
					description "Packets transmitted to the neighbour";
				}
				leaf packets-received-from-the-neighbour{
					config false;
					type uint16;
					description "Packets received from the neighbour";
				}
				leaf failed-transmits{
					config false;
					type uint16;
					description "Failed transmissions to the neighbour";
				}
			}
		}
		list neighbour-signal-levels{
			config false;
			key "macaddress";
			description "List of listen neighbours";
			leaf macaddress {
				config false;
				type string;
				description "Mac address of device";
			}
			list neighbour{
				key "neighbour-macaddress";
				leaf neighbour-macaddress {
					config false;
					type string;
					description "Neighbor Mac address";
				}
				leaf mean-rsl{
					config false;
					type int8;
					description "Mean RSL to the neighbour";
				}
			}
		}
	}
}
